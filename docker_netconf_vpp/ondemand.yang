module ondemand {
    namespace "urn:sysrepo:ondemand";
    prefix od;
    import ietf-inet-types {
      prefix inet;
    }

    revision 2022-02-17 {
        description "Initial revision.";
    }

    rpc add-route {
        description "Operation to add new route towards prefix.";

        input {
            leaf prefix {
                description "Parameter determining when to perform the operation.";
                type string;
            }
	    leaf destination {
		description "destination address.";
		type string;
	    }
        }
    }

    notification route-miss {
        description "test";
	leaf prefix {
		description "prefix";
		type string;
	}
    }
}
